DATA-WITH-EXTENDED-TYPE DEFINITIONS ::= BEGIN
Data-With-Extended-Type ::= [PRIVATE 48] IMPLICIT SEQUENCE 
{
    type [PRIVATE 51] IMPLICIT Extended-Type,
    dependencies [PRIVATE 71] IMPLICIT Tvb-Control OPTIONAL,
    data [PRIVATE 50] IMPLICIT Byte-Array256
}
Extended-Type ::= [PRIVATE 51] IMPLICIT UInt8
Tvb-Control ::= [PRIVATE 71] IMPLICIT SEQUENCE 
{
    data [PRIVATE 1] IMPLICIT BOOLEAN,
    serial [PRIVATE 1] IMPLICIT BOOLEAN,
    update-counter [PRIVATE 1] IMPLICIT BOOLEAN,
    attribute [PRIVATE 205] IMPLICIT Tvb-Attributes OPTIONAL
}
Tvb-Attributes ::= [PRIVATE 205] IMPLICIT INTEGER 
Byte-Array256 ::= [PRIVATE 50] IMPLICIT OCTET STRING 
UInt8 ::= [PRIVATE 31] IMPLICIT OCTET STRING 
END
