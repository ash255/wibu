EXT-CMACT-KEY DEFINITIONS ::= BEGIN
Ext-CmAct-Key ::= [PRIVATE 138] IMPLICIT SEQUENCE 
{
    cmact-serial-number [PRIVATE 126] IMPLICIT CmActSerial-ID
}
CmActSerial-ID ::= [PRIVATE 126] IMPLICIT OCTET STRING 

END
