LIF-CONTENT DEFINITIONS ::= BEGIN

LIF-Content ::= [PRIVATE 228] IMPLICIT SEQUENCE
{
    sw-specs[PRIVATE 161] IMPLICIT Software-Specs,
    clocks[PRIVATE 100] IMPLICIT Clocks,
    license-description[PRIVATE 125] IMPLICIT License-Description,
    binding[PRIVATE 136] IMPLICIT Binding-Scheme,
    cmact-options[PRIVATE 133] IMPLICIT CmAct-Options,
    mask[PRIVATE 142] IMPLICIT Mask OPTIONAL
}
Software-Specs ::= [PRIVATE 161] IMPLICIT SEQUENCE 
{
    creator-name[PRIVATE 181] IMPLICIT UTF8String,
    creator-version[PRIVATE 165] IMPLICIT Format-Version,
    required-version[PRIVATE 122] IMPLICIT Format-Version
}
Format-Version ::= [PRIVATE 122] IMPLICIT SEQUENCE 
{
    sfl[PRIVATE 78] IMPLICIT UInt8,
    sfh[PRIVATE 84] IMPLICIT UInt8,
    feature-flags[PRIVATE 32] IMPLICIT UInt32
}
UInt8 ::= [PRIVATE 31] IMPLICIT OCTET STRING 
UInt32 ::= [PRIVATE 34] IMPLICIT OCTET STRING 
Clocks ::= [PRIVATE 100] IMPLICIT SEQUENCE 
{
    box-time[PRIVATE 178] IMPLICIT Seconds-Since-2000,
    certified-time[PRIVATE 179] IMPLICIT Seconds-Since-2000
}
Seconds-Since-2000 ::= [PRIVATE 180] IMPLICIT UInt32
License-Description ::= [PRIVATE 125] IMPLICIT SEQUENCE 
{
    license-description[PRIVATE 30] IMPLICIT OCTET STRING, -- BMPString, it does't work well in asn1tools, beacase asn1tools only support utf-8, but here is utf-16
    firm-code[PRIVATE 114] IMPLICIT Firm-Code
}
Firm-Code ::= [PRIVATE 114] IMPLICIT OCTET STRING
Binding-Scheme ::= [PRIVATE 136] IMPLICIT SEQUENCE 
{
    cmact-id[PRIVATE 148] IMPLICIT CmAct-ID,
    telephone-id[PRIVATE 127] IMPLICIT Telephone-ID,
    binding-method[PRIVATE 128] EXPLICIT Binding-Method
}
CmAct-ID ::= [PRIVATE 148] IMPLICIT IA5String 
Telephone-ID ::= [PRIVATE 127] IMPLICIT OCTET STRING 
Binding-Method ::= CHOICE 
{
    smartbind[PRIVATE 129] IMPLICIT SmartBind-Parameters,
    custom-binding[PRIVATE 131] IMPLICIT CustomBinding-Parameters,
    dcbn-classic[PRIVATE 132] IMPLICIT DCBN-Parameters,
    nonebind[PRIVATE 231] IMPLICIT NULL,
    cm-server-ip[PRIVATE 232] IMPLICIT NULL,
    serial-number[PRIVATE 233] IMPLICIT NULL,
    random[PRIVATE 234] IMPLICIT NULL
}
SmartBind-Parameters ::= [PRIVATE 129] IMPLICIT SEQUENCE 
{
    heuristic[PRIVATE 31] IMPLICIT UInt8,
    redundancy-level[PRIVATE 130] IMPLICIT Redundancy-Level
}
Redundancy-Level ::= [PRIVATE 130] IMPLICIT OCTET STRING 
CustomBinding-Parameters ::= [PRIVATE 131] IMPLICIT IA5String 
DCBN-Parameters ::= [PRIVATE 132] IMPLICIT SEQUENCE 
{
    disk[PRIVATE 1] IMPLICIT BOOLEAN,
    cpu-type[PRIVATE 1] IMPLICIT BOOLEAN,
    board[PRIVATE 1] IMPLICIT BOOLEAN,
    network[PRIVATE 1] IMPLICIT BOOLEAN,
    tolerance[PRIVATE 2] IMPLICIT UInt8 OPTIONAL
}
CmAct-Options ::= [PRIVATE 133] IMPLICIT SEQUENCE 
{
    allow-vm[PRIVATE 219] IMPLICIT BOOLEAN,
    allow-reimport[PRIVATE 220] IMPLICIT BOOLEAN
}
Mask ::= [PRIVATE 142] IMPLICIT INTEGER 

END
