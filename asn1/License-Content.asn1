LICENSE-CONTENT DEFINITIONS ::= BEGIN
License-Content ::= [PRIVATE 229] IMPLICIT SEQUENCE
{
    sw-specs[PRIVATE 161] IMPLICIT Software-Specs,
    cmact-serial-id[PRIVATE 126] IMPLICIT CmActSerial-ID,
    lif[PRIVATE 4] IMPLICIT OCTET STRING,
    device-id[PRIVATE 190] IMPLICIT Device-ID OPTIONAL,
    pkcs7-elements[PRIVATE 160] IMPLICIT PKCS7-Content-List
}
Software-Specs ::= [PRIVATE 161] IMPLICIT SEQUENCE 
{
    creator-name[PRIVATE 181] IMPLICIT UTF8String,
    creator-version[PRIVATE 165] IMPLICIT Format-Version,
    required-version[PRIVATE 122] IMPLICIT Format-Version
}
Format-Version ::= [PRIVATE 122] IMPLICIT SEQUENCE 
{
    sfl[PRIVATE 78] IMPLICIT UInt8,
    sfh[PRIVATE 84] IMPLICIT UInt8,
    feature-flags[PRIVATE 32] IMPLICIT UInt32
}
UInt8 ::= [PRIVATE 31] IMPLICIT OCTET STRING 
UInt32 ::= [PRIVATE 34] IMPLICIT OCTET STRING 
CmActSerial-ID ::= [PRIVATE 126] IMPLICIT OCTET STRING 
Device-ID ::= [PRIVATE 190] IMPLICIT OCTET STRING 
PKCS7-Content-List ::= [PRIVATE 160] IMPLICIT SEQUENCE OF OCTET STRING

END
