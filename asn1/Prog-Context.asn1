PROG-CONTEXT DEFINITIONS ::= BEGIN

Prog-Context ::= [PRIVATE 96] IMPLICIT SEQUENCE
{
    container-type-specific[PRIVATE 99] EXPLICIT Container-Type-Specific,
    receiver-fi[PRIVATE 80] IMPLICIT PKCS7-Firm-Item OPTIONAL,
    receiver-pi[PRIVATE 85] IMPLICIT PKCS7-Product-Item-List
}
Container-Type-Specific ::= CHOICE
{
    cmact[PRIVATE 227] IMPLICIT CmAct-Specific,
    cmdongle[PRIVATE 199] IMPLICIT NULL,
    cmcloud[PRIVATE 200] IMPLICIT NULL
}
CmAct-Specific ::= [PRIVATE 227] IMPLICIT SEQUENCE 
{
    lif[PRIVATE 4] IMPLICIT OCTET STRING,
    is-running-in-vm[PRIVATE 1] IMPLICIT BOOLEAN,
    operating-system[PRIVATE 202] IMPLICIT Operating-System-Version,
    finger-print[PRIVATE 134] IMPLICIT Finger-Print,
    smartbind-inventory[PRIVATE 12] IMPLICIT UTF8String OPTIONAL,
    device-id[PRIVATE 190] IMPLICIT Device-ID OPTIONAL
}
Operating-System-Version ::= [PRIVATE 202] IMPLICIT INTEGER 
Finger-Print ::= [PRIVATE 134] IMPLICIT SEQUENCE 
{
    host-info[PRIVATE 201] IMPLICIT Host-Info-Version,
    host-info-name[PRIVATE 12] IMPLICIT UTF8String
}
Host-Info-Version ::= [PRIVATE 201] IMPLICIT SEQUENCE OF [PRIVATE 32] IMPLICIT UInt16
UInt16 ::= [PRIVATE 32] IMPLICIT OCTET STRING 
Device-ID ::= [PRIVATE 190] IMPLICIT OCTET STRING 
PKCS7-Firm-Item ::= [PRIVATE 80] IMPLICIT SEQUENCE 
{
    fi-p[PRIVATE 168] IMPLICIT OCTET STRING OPTIONAL,
    fi-t[PRIVATE 169] IMPLICIT OCTET STRING OPTIONAL,
    fi-dynamic[PRIVATE 171] IMPLICIT OCTET STRING OPTIONAL,
    fi-delete[PRIVATE 172] IMPLICIT OCTET STRING OPTIONAL
}
PKCS7-Product-Item-List ::= [PRIVATE 85] IMPLICIT SEQUENCE OF [PRIVATE 81] EXPLICIT PKCS7-Product-Item
PKCS7-Product-Item ::= [PRIVATE 81] IMPLICIT SEQUENCE 
{
    pi-p[PRIVATE 173] IMPLICIT OCTET STRING OPTIONAL,
    pi-t[PRIVATE 174] IMPLICIT OCTET STRING OPTIONAL,
    pi-dynamic[PRIVATE 176] IMPLICIT OCTET STRING OPTIONAL,
    pi-merge[PRIVATE 139] IMPLICIT OCTET STRING OPTIONAL,
    pi-delete[PRIVATE 177] IMPLICIT OCTET STRING OPTIONAL
}

END
