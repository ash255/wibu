PROG-UPDATE DEFINITIONS ::= BEGIN

Prog-Update ::= [PRIVATE 107] IMPLICIT SEQUENCE
{
    fi[PRIVATE 80] IMPLICIT PKCS7-Firm-Item OPTIONAL,
    pi[PRIVATE 85] IMPLICIT PKCS7-Product-Item-List,
    expected-firm-update-counter[PRIVATE 137] IMPLICIT UInt32,
    device-id[PRIVATE 190] IMPLICIT Device-ID OPTIONAL
}
PKCS7-Firm-Item ::= [PRIVATE 80] IMPLICIT SEQUENCE 
{
    fi-p[PRIVATE 168] IMPLICIT OCTET STRING OPTIONAL,
    fi-t[PRIVATE 169] IMPLICIT OCTET STRING OPTIONAL,
    fi-dynamic[PRIVATE 171] IMPLICIT OCTET STRING OPTIONAL,
    fi-delete[PRIVATE 172] IMPLICIT OCTET STRING OPTIONAL
}
PKCS7-Product-Item-List ::= [PRIVATE 85] IMPLICIT SEQUENCE OF [PRIVATE 81] IMPLICIT PKCS7-Product-Item
PKCS7-Product-Item ::= [PRIVATE 81] IMPLICIT SEQUENCE 
{
    pi-p[PRIVATE 173] IMPLICIT OCTET STRING OPTIONAL,
    pi-t[PRIVATE 174] IMPLICIT OCTET STRING OPTIONAL,
    pi-dynamic[PRIVATE 176] IMPLICIT OCTET STRING OPTIONAL,
    pi-merge[PRIVATE 139] IMPLICIT OCTET STRING OPTIONAL,
    pi-delete[PRIVATE 177] IMPLICIT OCTET STRING OPTIONAL
}
UInt32 ::= [PRIVATE 34] IMPLICIT OCTET STRING 
Device-ID ::= [PRIVATE 190] IMPLICIT OCTET STRING 

END
